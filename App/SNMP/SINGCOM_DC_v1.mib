-- ===========================================================================
-- This file defines top level (general) mib for Converter
-- All the specific Converter should have agent capabilities 
-- @Author: Singcom Microwave Communication
-- @Date: 25-07-2016
-- Version: 1.0.0
-- Revision History
-- ---------------------------------------------------------------------------
-- Author     Revision Date   Change Definition                             
-- ---------------------------------------------------------------------------
-- Singcom Microwave Communication   25-07-2016      Initial Creation
-- ===========================================================================

SINGCOM-Converter-MIB DEFINITIONS ::= BEGIN

IMPORTS 
	NOTIFICATION-TYPE, MODULE-IDENTITY, OBJECT-TYPE, 
	enterprises,
	IpAddress,
    TimeTicks,
	Integer32
		FROM SNMPv2-SMI
	NOTIFICATION-GROUP, OBJECT-GROUP, MODULE-COMPLIANCE
		FROM SNMPv2-CONF
	DisplayString
		FROM SNMPv2-TC
	TEXTUAL-CONVENTION
		FROM SNMPv2-TC;

singcom MODULE-IDENTITY
	LAST-UPDATED "201607250808Z"
	ORGANIZATION 
		"Singcom Microwave Communication Pte. Ltd.,Singapore"
	CONTACT-INFO 
		"Singcom Microwave Communication Pte. Ltd."
	DESCRIPTION 
		"Monitor & Control Information of Converter"
::= { enterprises 18210 }

products MODULE-IDENTITY
	LAST-UPDATED "201607250808Z"
	ORGANIZATION 
		"Singcom Microwave Communication Pte. Ltd.,Singapore"
	CONTACT-INFO 
		"Singcom Microwave Communication Pte. Ltd."
	DESCRIPTION 
		"Monitor & Control Information of Converter"
::= { singcom 2 }

Converter MODULE-IDENTITY
	LAST-UPDATED "201607250808Z"
	ORGANIZATION 
		"Singcom Microwave Communication Pte. Ltd.,Singapore"
	CONTACT-INFO 
		"Singcom Microwave Communication Pte. Ltd."
	DESCRIPTION 
		"Monitor & Control Information of Converter"
	REVISION "201607250808Z"
	DESCRIPTION 
		"Monitor & Control Information of Converter"
::= { products 13 }

-- System Information
system OBJECT IDENTIFIER ::= { Converter 1 }

sysDescr OBJECT-TYPE
	SYNTAX	DisplayString (SIZE (0..30))
	MAX-ACCESS	read-write
	STATUS	current
	DESCRIPTION
		"A textual description of the entity. This value should include
		 the full name and version identification of the system's hardware
		 type, software operating-system, and networking software. It is
		 mandatory that this only contain printable ASCII characters.
		 DEFAULT SETTING: FASTCOMM Converter"
::= { system 1 }

sysUpTime	OBJECT-TYPE
	SYNTAX	TimeTicks
	MAX-ACCESS	read-only
	STATUS	current
	DESCRIPTION
		"The time (in hundredths of a second) since the network management
		 portion of the system was last re-initialized."
::= { system 2 }

sysContact OBJECT-TYPE
	SYNTAX	DisplayString (SIZE (0..30))
	MAX-ACCESS	read-write
	STATUS	current
	DESCRIPTION
		"The textual identification of the contact person for this managed
         node, together with information on how to contact this person.
         DEFAULT SETTING: Customer-Service +65-63974868"
::= { system 3 }

sysName OBJECT-TYPE
	SYNTAX	DisplayString (SIZE (0..30))
	MAX-ACCESS	read-write
	STATUS	current
	DESCRIPTION
		"An administratively-assigned name for this managed node. By
         convention, this is the node's fully-qualified domain name.
         DEFAULT SETTING: Converter"
::= { system 4 }

sysLocation OBJECT-TYPE
	SYNTAX	DisplayString (SIZE (0..30))
	MAX-ACCESS	read-write
	STATUS	current
	DESCRIPTION
      	"The physical location of this node.
      	 DEFAULT SETTING: SINGCOM, SINGAPORE"
::= { system 5 }

-- Device Information
deviceInfo OBJECT IDENTIFIER ::= { Converter 2 }

managerIP OBJECT-TYPE
	SYNTAX	IpAddress
	MAX-ACCESS	read-write
	STATUS	current
	DESCRIPTION
		"Manager's IP address where trap will be sent
		 DEFAULT SETTING: 192.168.1.10"
::= { deviceInfo 1 }

deviceIP OBJECT-TYPE
	SYNTAX	IpAddress
	MAX-ACCESS	read-write
	STATUS	current
	DESCRIPTION
		"IP address of the device
		 DEFAULT SETTING: 192.168.1.1"
::= { deviceInfo 2 }

firmwareVersion OBJECT-TYPE
	SYNTAX	DisplayString (SIZE (0..30))
	MAX-ACCESS	read-only
	STATUS	current
	DESCRIPTION
		"Firmware version of the device."
::= { deviceInfo 3 }

-- Device operation
deviceOperation OBJECT IDENTIFIER ::= {Converter 3}
converterALOFreq OBJECT-TYPE
	SYNTAX	DisplayString (SIZE (0..30))
	MAX-ACCESS	read-write
	STATUS	current
	DESCRIPTION
		"Get/Set Converter A LO Frequency"
::= {deviceOperation 1}						

converterBLOFreq OBJECT-TYPE
	SYNTAX	DisplayString (SIZE (0..30))
	MAX-ACCESS	read-write
	STATUS	current
	DESCRIPTION
		"Get/Set Converter B LO Frequency"
::= {deviceOperation 2}						

converterAAtten OBJECT-TYPE
	SYNTAX	DisplayString (SIZE (0..30))
	MAX-ACCESS	read-write
	STATUS	current
	DESCRIPTION
		"Get/Set Converter A Attenuation"
::= {deviceOperation 3}						

converterBAtten OBJECT-TYPE
	SYNTAX	DisplayString (SIZE (0..30))
	MAX-ACCESS	read-write
	STATUS	current
	DESCRIPTION
		"Get/Set Converter B Attenuation"
::= {deviceOperation 4}						


-- Device Alarm
deviceAlarm OBJECT IDENTIFIER ::= {Converter 4}

converterAAlarm OBJECT-TYPE
	SYNTAX	INTEGER { notApplicable(2), ok(1), alarm(0) }
	MAX-ACCESS	read-only
	STATUS	current
	DESCRIPTION
		"Converter A alarm status"
::= {deviceAlarm 1}				

converterBAlarm OBJECT-TYPE
	SYNTAX	INTEGER { notApplicable(2), ok(1), alarm(0) }
	MAX-ACCESS	read-only
	STATUS	current
	DESCRIPTION
		"Converter B alarm status"
::= {deviceAlarm 2}				


-- Traps
deviceTraps OBJECT IDENTIFIER ::= {Converter 5}

converterATrap	NOTIFICATION-TYPE
	OBJECTS{converterAAlarm}
	STATUS     current
	DESCRIPTION
         "The trap indicates the Converter A status"
::= {deviceTraps 1}

converterBTrap	NOTIFICATION-TYPE
	OBJECTS{converterBAlarm}
	STATUS     current
	DESCRIPTION
         "The trap indicates the Converter B status"
::= {deviceTraps 2}
      
END
