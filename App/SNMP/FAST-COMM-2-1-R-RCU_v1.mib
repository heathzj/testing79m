-- ===========================================================================
-- This file defines top level (general) mib for RCU
-- All the specific RCU should have agent capabilities 
-- @Author: Fastcomm
-- @Date: 25-02-2016
-- Version: 1.0.1
-- Revision History
-- ---------------------------------------------------------------------------
-- Author     Revision Date   Change Definition                             
-- ---------------------------------------------------------------------------
-- Fastcomm   25-02-2016      Initial Creation
-- ===========================================================================

FASTCOMM-RCU-MIB DEFINITIONS ::= BEGIN

IMPORTS 
	NOTIFICATION-TYPE, MODULE-IDENTITY, OBJECT-TYPE, 
	enterprises,
	IpAddress,
    TimeTicks,
	Integer32
		FROM SNMPv2-SMI
	NOTIFICATION-GROUP, OBJECT-GROUP, MODULE-COMPLIANCE
		FROM SNMPv2-CONF
	DisplayString
		FROM SNMPv2-TC
	TEXTUAL-CONVENTION
		FROM SNMPv2-TC;

fastcomm MODULE-IDENTITY
	LAST-UPDATED "201602250808Z"
	ORGANIZATION 
		"Fastcomm Communication Technologies Pte. Ltd.,Singapore"
	CONTACT-INFO 
		"Fastcomm Communication Technologies Pte. Ltd."
	DESCRIPTION 
		"Monitor & Control Information of RCU"
::= { enterprises 18210 }

products MODULE-IDENTITY
	LAST-UPDATED "201602250808Z"
	ORGANIZATION 
		"Fastcomm Communication Technologies Pte. Ltd.,Singapore"
	CONTACT-INFO 
		"Fastcomm Communication Technologies Pte. Ltd."
	DESCRIPTION 
		"Monitor & Control Information of RCU"
::= { fastcomm 2 }

rcu MODULE-IDENTITY
	LAST-UPDATED "201602250808Z"
	ORGANIZATION 
		"Fastcomm Communication Technologies Pte. Ltd.,Singapore"
	CONTACT-INFO 
		"Fastcomm Communication Technologies Pte. Ltd."
	DESCRIPTION 
		"Monitor & Control Information of RCU"
	REVISION "201602250808Z"
	DESCRIPTION 
		"Monitor & Control Information of RCU"
::= { products 13 }

-- System Information
system OBJECT IDENTIFIER ::= { rcu 1 }

sysDescr OBJECT-TYPE
	SYNTAX	DisplayString (SIZE (0..30))
	MAX-ACCESS	read-write
	STATUS	current
	DESCRIPTION
		"A textual description of the entity. This value should include
		 the full name and version identification of the system's hardware
		 type, software operating-system, and networking software. It is
		 mandatory that this only contain printable ASCII characters.
		 DEFAULT SETTING: FASTCOMM RCU"
::= { system 1 }

sysUpTime	OBJECT-TYPE
	SYNTAX	TimeTicks
	MAX-ACCESS	read-only
	STATUS	current
	DESCRIPTION
		"The time (in hundredths of a second) since the network management
		 portion of the system was last re-initialized."
::= { system 2 }

sysContact OBJECT-TYPE
	SYNTAX	DisplayString (SIZE (0..30))
	MAX-ACCESS	read-write
	STATUS	current
	DESCRIPTION
		"The textual identification of the contact person for this managed
         node, together with information on how to contact this person.
         DEFAULT SETTING: Customer-Service +65-63974868"
::= { system 3 }

sysName OBJECT-TYPE
	SYNTAX	DisplayString (SIZE (0..30))
	MAX-ACCESS	read-write
	STATUS	current
	DESCRIPTION
		"An administratively-assigned name for this managed node. By
         convention, this is the node's fully-qualified domain name.
         DEFAULT SETTING: RCU"
::= { system 4 }

sysLocation OBJECT-TYPE
	SYNTAX	DisplayString (SIZE (0..30))
	MAX-ACCESS	read-write
	STATUS	current
	DESCRIPTION
      	"The physical location of this node.
      	 DEFAULT SETTING: FASTCOMM, SINGAPORE"
::= { system 5 }

-- Device Information
deviceInfo OBJECT IDENTIFIER ::= { rcu 2 }

managerIP OBJECT-TYPE
	SYNTAX	IpAddress
	MAX-ACCESS	read-write
	STATUS	current
	DESCRIPTION
		"Manager's IP address where trap will be sent
		 DEFAULT SETTING: 192.168.1.10"
::= { deviceInfo 1 }

deviceIP OBJECT-TYPE
	SYNTAX	IpAddress
	MAX-ACCESS	read-write
	STATUS	current
	DESCRIPTION
		"IP address of the device
		 DEFAULT SETTING: 192.168.1.1"
::= { deviceInfo 2 }

firmwareVersion OBJECT-TYPE
	SYNTAX	DisplayString (SIZE (0..30))
	MAX-ACCESS	read-only
	STATUS	current
	DESCRIPTION
		"Firmware version of the device."
::= { deviceInfo 3 }

-- Device operation
deviceOperation OBJECT IDENTIFIER ::= {rcu 3}
switchMode OBJECT-TYPE
	SYNTAX	INTEGER { manual(1), auto(0) }
	MAX-ACCESS	read-write
	STATUS	current
	DESCRIPTION
		"Get/Set switch mode"
::= {deviceOperation 1}						

localMode OBJECT-TYPE
	SYNTAX	INTEGER { local(1), remote(0) }
	MAX-ACCESS	read-only
	STATUS	current
	DESCRIPTION
		"Get local mode"
::= {deviceOperation 2}						

reference OBJECT-TYPE
	SYNTAX	INTEGER { on(1), off(0) }
	MAX-ACCESS	read-write
	STATUS	current
	DESCRIPTION
		"Get/Set 10MHz Reference"
::= {deviceOperation 3}						

rfSW1 OBJECT-TYPE
	SYNTAX	INTEGER { pos-2(2), pos-1(1), unknown(0) }
	MAX-ACCESS	read-write
	STATUS	current
	DESCRIPTION
		"Get/Set RF SW1 position"
::= {deviceOperation 4}

rfSW2 OBJECT-TYPE
	SYNTAX	INTEGER { pos-2(2), pos-1(1), unknown(0) }
	MAX-ACCESS	read-write
	STATUS	current
	DESCRIPTION
		"Get/Set RF SW2 position"
::= {deviceOperation 5}

ifSWA OBJECT-TYPE
	SYNTAX	INTEGER { pos-2(2), pos-1(1), unknown(0) }
	MAX-ACCESS	read-write
	STATUS	current
	DESCRIPTION
		"Get/Set IF SW1 position"
::= {deviceOperation 6}

ifSWB OBJECT-TYPE
	SYNTAX	INTEGER { pos-2(2), pos-1(1), unknown(0) }
	MAX-ACCESS	read-write
	STATUS	current
	DESCRIPTION
		"Get/Set IF SW2 position"
::= {deviceOperation 7}

-- Device Alarm
deviceAlarm OBJECT IDENTIFIER ::= {rcu 4}

lnbAAlarm OBJECT-TYPE
	SYNTAX	INTEGER { notApplicable(2), ok(1), alarm(0) }
	MAX-ACCESS	read-only
	STATUS	current
	DESCRIPTION
		"LNB A alarm status"
::= {deviceAlarm 1}				

lnbBAlarm OBJECT-TYPE
	SYNTAX	INTEGER { notApplicable(2), ok(1), alarm(0) }
	MAX-ACCESS	read-only
	STATUS	current
	DESCRIPTION
		"LNB B alarm status"
::= {deviceAlarm 2}				

lnbCAlarm OBJECT-TYPE
	SYNTAX	INTEGER { notApplicable(2), ok(1), alarm(0) }
	MAX-ACCESS	read-only
	STATUS	current
	DESCRIPTION
		"LNB C alarm status"
::= {deviceAlarm 3}				

rfSW1Alarm OBJECT-TYPE
	SYNTAX	INTEGER { notApplicable(2), ok(1), alarm(0) }
	MAX-ACCESS	read-only
	STATUS	current
	DESCRIPTION
		"RF SW1 alarm status"
::= {deviceAlarm 4}				

rfSW2Alarm OBJECT-TYPE
	SYNTAX	INTEGER { notApplicable(2), ok(1), alarm(0) }
	MAX-ACCESS	read-only
	STATUS	current
	DESCRIPTION
		"RF SW2 alarm status"
::= {deviceAlarm 5}				

ifSWAAlarm OBJECT-TYPE
	SYNTAX	INTEGER { notApplicable(2), ok(1), alarm(0) }
	MAX-ACCESS	read-only
	STATUS	current
	DESCRIPTION
		"IF SWA alarm status"
::= {deviceAlarm 6}				

ifSWBAlarm OBJECT-TYPE
	SYNTAX	INTEGER { notApplicable(2), ok(1), alarm(0) }
	MAX-ACCESS	read-only
	STATUS	current
	DESCRIPTION
		"IF SWB alarm status"
::= {deviceAlarm 7}				

ps1Alarm OBJECT-TYPE
	SYNTAX	INTEGER { notApplicable(2), ok(1), alarm(0) }
	MAX-ACCESS	read-only
	STATUS	current
	DESCRIPTION
		"Power Supply 1 alarm status"
::= {deviceAlarm 8}				

ps2Alarm OBJECT-TYPE
	SYNTAX	INTEGER { notApplicable(2), ok(1), alarm(0) }
	MAX-ACCESS	read-only
	STATUS	current
	DESCRIPTION
		"Power Supply 2 alarm status"
::= {deviceAlarm 9}				

-- Traps
deviceTraps OBJECT IDENTIFIER ::= {rcu 5}

lnbATrap	NOTIFICATION-TYPE
	OBJECTS{lnbAAlarm}
	STATUS     current
	DESCRIPTION
         "The trap indicates the LNB A status"
::= {deviceTraps 1}

lnbBTrap	NOTIFICATION-TYPE
	OBJECTS{lnbBAlarm}
	STATUS     current
	DESCRIPTION
         "The trap indicates the LNB B status"
::= {deviceTraps 2}

lnbCTrap	NOTIFICATION-TYPE
	OBJECTS{lnbCAlarm}
	STATUS     current
	DESCRIPTION
         "The trap indicates the LNB C status"
::= {deviceTraps 3}

rfSW1Trap	NOTIFICATION-TYPE
	OBJECTS{rfSW1Alarm}
	STATUS     current
	DESCRIPTION
         "The trap indicates the RF SW1 status"
::= {deviceTraps 4}

rfSW2Trap	NOTIFICATION-TYPE
	OBJECTS{rfSW2Alarm}
	STATUS     current
	DESCRIPTION
         "The trap indicates the RF SW2 status"
::= {deviceTraps 5}

ifSWATrap	NOTIFICATION-TYPE
	OBJECTS{ifSWAAlarm}
	STATUS     current
	DESCRIPTION
         "The trap indicates the IF SWA status"
::= {deviceTraps 6}

ifSWBTrap	NOTIFICATION-TYPE
	OBJECTS{ifSWBAlarm}
	STATUS     current
	DESCRIPTION
         "The trap indicates the IF SWB status"
::= {deviceTraps 7}

ps1Trap	NOTIFICATION-TYPE
	OBJECTS{ps1Alarm}
	STATUS     current
	DESCRIPTION
         "The trap indicates the Power Supply 1 status"
::= {deviceTraps 8}

ps2Trap	NOTIFICATION-TYPE
	OBJECTS{ps2Alarm}
	STATUS     current
	DESCRIPTION
         "The trap indicates the Power Supply 2 status"
::= {deviceTraps 9}

      
END
